(defun c:lsr (/ cmde NomFichier Texte Point)
  (setq	cmde	   (getvar "CMDECHO")
	NomFichier (str2lst (vlax-get-property (vla-get-ActiveDocument (vlax-get-Acad-Object)) 'NAME)
			    "-"
			    )
	)
  (setvar "CMDECHO" 0)
;;;  (cond	((>= (length NomFichier) 4) (setq Texte (strcat (nth 2 NomFichier) "-" (nth 3 NomFichier))))
;;;	(t (setq Texte (car NomFichier)))
;;;	)
  (cond	((>= (length NomFichier) 4) (setq Texte (nth 3 NomFichier)))
	(t (setq Texte (car NomFichier)))
	)
  (if (not (tblsearch "STYLE" "Laser"))
    (progn (princ "\nCréation du style \"Laser\"")
	   (command "-STYLE" "Laser" "monotxt.shx" 10 1 0 "_n" "_n" "_n")
	   )
    )
  (setq Point (getpoint "\nPoint d'insertion du texte : "))
  (if (entmake (list '(0 . "TEXT")
		     '(67 . 0)
		     '(410 . "Model")
		     '(8 . "0")
		     '(100 . "AcDbText")
		     (cons 10 Point)
		     '(40 . 5)
		     (cons 1 Texte)
		     '(7 . "Laser")
		     '(72 . 4)
		     (cons 11 (mapcar '+ Point '(1 0 0)))
		     '(73 . 2)
		     )
	       )
    (princ Texte)
    (princ "Erreur")
    )
  (Modtxtexp (entlast))
  (setvar "CMDECHO" cmde)
  (princ)
  )
