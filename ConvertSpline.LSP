(defun c:cvsp ( / sset i ent)
  (setq sset (ssget '((0 . "SPLINE")))
	i 0)
  (repeat (sslength sset)
    (setq ent (ssname sset i)
	  i (1+ i)
	  )
    (command "_splinedit" ent "P" 2)
    )
  (setq sset nil)
  )

(defun c:sai ( / sset i ent)
  (setq sset (ssget)
	i 0)
  (command "aire" "A" "O")
  (repeat (sslength sset)
    (setq ent (ssname sset i)
	  i (1+ i)
	  )
    (command ent)
    )
  (setq sset nil)
  )
