(vl-load-com)

(defun c:S2A4 (/ Spline Dev_max)
  (if (and (setq Spline (car (entsel "\nSélectionnez une Spline : ")))
	   (= (cdr (assoc 0 (entget Spline))) "SPLINE")
	   )
    (convert_spline_to_arc Spline)
    (prompt "\nCe n'est pas une spline.")
    )
  (princ)
  )

(defun convert_spline_to_arc (Spline /)
  (setq	SplineDxfData (entget Spline)
	MaxParam      (apply 'max (dxf '40 SplineDxfData))
	NbDiv	      (1- (car (dxf '73 SplineDxfData)))
	ListeParam    (ListeCumul MaxParam NbDiv)
	Spline_Vl     (vlax-ename->vla-object Spline)
	Points	      (mapcar (function (lambda (p) (vlax-curve-getPointAtParam Spline_Vl p))) ListeParam)
	)
  (princ Param)
  (princ)
  (mapcar '(lambda (x) (make_point x '0)) Points)
  )

(defun ListeNb (n nb / liste) (repeat nb (setq liste (cons n liste))) liste)

(defun dxf (code alst)
  (apply 'append
	 (mapcar (function (lambda (x)
			     (if (= (car x) code)
			       (list (cdr x))
			       )
			     )
			   )
		 alst
		 )
	 )
  )

(defun nthcdr (i lst) (repeat i (setq lst (cdr lst))) lst)

(defun ListeCumul (Lg Nb / liste div)
  (setq	liste (list Lg)
	div   (/ Lg Nb)
	)
  (repeat Nb (setq liste (cons (- (car liste) div) liste)))
  (cons 0 (cdr liste))
  )
